module ieee802-dot1cb-frer-types {
  yang-version 1.1;
  namespace "urn:ieee:std:802.1Q:yang:ieee802-dot1cb-frer-types";
  prefix dot1cb-frer-types;

  organization
    "Institute of Electrical and Electronics Engineers";
  contact
    "WG-URL: http://ieee802.org/1/
     WG-EMail: stds-802-1-l@ieee.org

     Contact: IEEE 802.1 Working Group Chair
     Postal: C/O IEEE 802.1 Working Group
            IEEE Standards Association
            445 Hoes Lane
            Piscataway, NJ 08854
            USA

     E-mail: stds-802-1-chairs@ieee.org";
  description
    "Management objects that control the frame replication and
     elimination from IEEE Std 802.1CB-2017. This YANG data model conforms
     to the Network Management Datastore Architecture defined in RFC 8342.
     Copyright (C) IEEE (2021). This version of this YANG module is part
     of IEEE Std 802.1CBcv; see the standard itself for full legal
     notices.";

  revision 2021-12-08 {
    description
      "Published as part of IEEE Std 802.1CBcv-2021. Initial version.";
    reference
      "IEEE Std 802.1CBcv-2021, Frame Replication and Elimination for
       Reliability - FRER YANG Data Model and Management Information Base
       Module.";
  }

  typedef seq-rcvy-algorithm {
    type enumeration {
      enum vector {
        value 0;
        description
          "The sequence recovery type used for the Vector Recovery
           Algorithm.";
      }
      enum match {
        value 1;
        description
          "The sequence recovery type used for the Match Recovery
           Algorithm.";
      }
    }
    description
      "An enumerated value specifying which sequence recovery algorithm
       is to be used for an instance of the Sequence recovery function.";
    reference
      "10.4.1.5 of IEEE Std 802.1CB-2017";
  }

  typedef seq-encaps-method {
    type enumeration {
      enum reserved {
        value 0;
        description
          "Reserved value.";
      }
      enum r-tag {
        value 1;
        description
          "The sequence encode decode type used for the R_TAG
           encode/decode method.";
      }
      enum hsr-seq-tag {
        value 2;
        description
          "The sequence encode decode type used for the HSR encode/decode
           method.";
      }
      enum prp-seq-trailer {
        value 3;
        description
          "The sequence encode decode type used for the PRP encode/decode
           method.";
      }
    }
    description
      "An enumerated value indicating the type of encapsulation used for
       an instance of the Sequence encode/decode function.";
    reference
      "10.5.1.5 of IEEE Std 802.1CB-2017";
  }
}
